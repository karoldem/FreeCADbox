class greekParent:
	
	def __init__(self,x,y, xy):
		self.x = x
		self.y = y
		self.xy = xy
		self.history = []
	
	
	def move(self, length, pattern = None):
		
		if pattern is not None:
			length = pattern(self,length)
		
		if self.xy == 'x':
			
			Gui.ActiveDocument.getInEdit().Object.addGeometry(Part.LineSegment(
				App.Vector(     0.001*self.x,          0.001*(self.y),            0),
				App.Vector(     0.001*(self.x+length), 0.001*(self.y),            0)),
				False)
			
			self.x += length
			self.xy = 'y'
			
		else:
			
			Gui.ActiveDocument.getInEdit().Object.addGeometry(Part.LineSegment(
				App.Vector(     0.001*self.x,          0.001*(self.y),            0),
				App.Vector(     0.001*(self.x),        0.001*(self.y+length),     0)),
				False)
			
			self.y += length
			self.xy = 'x'
		
		self.history.append(length)


def zPattern(self,length):
	return length if self.history[-2] > 0 else -length

def cPattern(self,length):
	return -length if self.history[-2] > 0 else length

def rightPattern(self,length):
	
	if self.xy == 'x':
		return length if self.history[-1] > 0 else -length
	
	if self.xy == 'y':
		return -length if self.history[-1] > 0 else length

def leftPattern(self,length):
	
	if self.xy == 'x':
		return -length if self.history[-1] > 0 else length
	
	if self.xy == 'y':
		return length if self.history[-1] > 0 else -length

class teeth:
	antiAccidentalOverrideVariable = 'AN6C_P5R6_Y1ES'

class greek(greekParent):
	
	def steps(self, steps, direction, moveAfter, moveBefore = None):
		
		if moveBefore is not None:
			if 'pattern' in moveBefore:
				self.move( moveBefore['length'], moveBefore['pattern'] )
			else:
				self.move( moveBefore['length'] )
		
		currentLevel= 0
		parent = greekParent(self.x, self.y, self.xy)
		parent.history = list(self.history)
		
		for i in steps:
			parent.move(i[0] - currentLevel, direction)
			currentLevel = i[0]
			parent.move(i[1], zPattern)
		
		parent.move(-currentLevel, direction)
		
		parent.move(moveAfter, zPattern)
	
	def teeth(self, teethNumber, width, space, depth, direction, moveAfter, moveBefore = None):
		
		if moveBefore is not None:
			if 'pattern' in moveBefore:
				self.move( moveBefore['length'], moveBefore['pattern'] )
			else:
				self.move( moveBefore['length'] )
		
		parent = greekParent(self.x, self.y, self.xy)
		parent.history = list(self.history)
		
		parent.move(depth, direction)
		parent.move(width, zPattern)
		parent.move(depth, cPattern)
		
		for i in range(teethNumber-1):
			parent.move(space, zPattern)
			parent.move(depth, cPattern)
			parent.move(width, zPattern)
			parent.move(depth, cPattern)
		
		parent.move(moveAfter, zPattern)
				
		self.x = parent.x
		self.y = parent.y
		self.xy = parent.xy
		
		return { 'teethNumber':teethNumber, 'width':width, 'space':space, 'depth':depth, 'moveAfter':moveAfter, 'moveBefore':moveBefore }
	
	def loadTeeth( self, args, direction ):
		self.teeth( args['teethNumber'], args['width'], args['space'], args['depth'], direction, args['moveAfter'], args['moveBefore'] )
	
	def fitTeeth(self, length, width, space):
		return (  (length+space)//(width+space), ((length+space)//(width+space))*(width+space) - space  )


thickness = 3500
heights = [50, 300, 250, 250, 200, 150]
heights = [i*1000 for i in heights]
middle = 250*1000
width = 500*1000
rightSide = (width - middle)//2
leftSide = width - middle - rightSide
depth = 200*1000
frontHeight = 50*1000



k = greek(0,0,'x')

fitTeeth = k.fitTeeth(rightSide - 6*thickness, thickness, thickness)

p= [rightSide - fitTeeth[1] - (rightSide - fitTeeth[1])//2,
	fitTeeth[1],
	(rightSide - fitTeeth[1])//2,
	fitTeeth[0]]

fitTeeth = k.fitTeeth(middle - 8*thickness, thickness, thickness)

q= [middle - fitTeeth[1] - (middle - fitTeeth[1])//2 - thickness,
	fitTeeth[1],
	(middle - fitTeeth[1])//2 - thickness,
	fitTeeth[0]]

fitTeeth = k.fitTeeth(leftSide - 6*thickness, thickness, thickness)

r= [leftSide - fitTeeth[1] - (leftSide - fitTeeth[1])//2,
	fitTeeth[1],
	(leftSide - fitTeeth[1])//2,
	fitTeeth[0]]

Teeth = {
	'teethNumber': p[3],
	'width':       thickness,
	'space':       thickness,
	'depth':       thickness,
	'moveAfter':   p[2] + thickness + q[0],
	'moveBefore':  {'length' :p[0] }   }

k.loadTeeth( Teeth, leftPattern )

Teeth = {
	'teethNumber': q[3],
	'width':       thickness,
	'space':       thickness,
	'depth':       thickness,
	'moveAfter':   q[2] + thickness + r[0],
	'moveBefore':  None  }

k.loadTeeth( Teeth, leftPattern )

Teeth = {
	'teethNumber': r[3],
	'width':       thickness,
	'space':       thickness,
	'depth':       thickness,
	'moveAfter':   r[2],
	'moveBefore':  None  }

k.loadTeeth( Teeth, leftPattern )

fitTeeth = k.fitTeeth(frontHeight - 6*thickness, thickness, thickness)

s = {
	'teethNumber': fitTeeth[0],
	'width':       thickness,
	'space':       thickness,
	'depth':       thickness,
	'moveAfter':   frontHeight - (frontHeight - fitTeeth[1])//2 - fitTeeth[1],
	'moveBefore':  { 'length': (frontHeight - fitTeeth[1])//2, 'pattern': leftPattern}  }

k.loadTeeth( s, leftPattern )
k.move(width, leftPattern)
k.loadTeeth( s, leftPattern )



Gui.ActiveDocument.getInEdit().Object.addConstraint(Sketcher.Constraint('Vertical',0)) 
Gui.ActiveDocument.getInEdit().Object.delConstraint(0)
